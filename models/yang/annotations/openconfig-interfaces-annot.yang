module openconfig-interfaces-annot {

    yang-version "1";

    namespace "http://openconfig.net/yang/annotation/openconfig-interfaces-annot";
    prefix "oc-interfaces-annot";

    import sonic-extensions { prefix sonic-ext; }
    import openconfig-interfaces { prefix oc-intf; }
    import openconfig-pins-interfaces { prefix "pins-if"; }
    import openconfig-p4rt { prefix "p4rt-if"; }
    import google-pins-interfaces { prefix "google-pins-if"; }
    import openconfig-if-ethernet {prefix oc-eth; }
    import openconfig-if-ip {prefix oc-ip; }
    import openconfig-if-aggregate { prefix oc-lag; }
    import openconfig-platform-port { prefix "oc-plat-port"; }
    import openconfig-platform-transceiver { prefix "oc-plat-xcvr"; }

    import openconfig-inet-types { prefix oc-inet; }

    deviation /oc-intf:interfaces/oc-intf:interface {
        deviate add {
            sonic-ext:key-transformer "intf_tbl_key_xfmr";
            sonic-ext:table-transformer "intf_table_xfmr";
            sonic-ext:path-transformer "intf_path_xfmr";
        }
    }

    deviation /oc-intf:interfaces/oc-intf:interface/oc-eth:ethernet/oc-eth:config {
        deviate add {
            sonic-ext:subtree-transformer "intf_eth_port_config_xfmr";
        }
    }

    deviation /oc-intf:interfaces/oc-intf:interface/oc-eth:ethernet/oc-eth:state {
        deviate add {
            sonic-ext:db-name "APPL_STATE_DB";
        }
    }

    deviation /oc-intf:interfaces/oc-intf:interface/oc-eth:ethernet/oc-eth:state/oc-eth:auto-negotiate {
        deviate add {
            sonic-ext:field-transformer "intf_eth_auto_neg_xfmr";
        }
    }

    deviation /oc-intf:interfaces/oc-intf:interface/oc-eth:ethernet/oc-eth:state/oc-eth:port-speed {
        deviate add {
            sonic-ext:field-transformer "intf_eth_port_speed_xfmr";
            sonic-ext:field-name "speed";
        }
    }

    deviation /oc-intf:interfaces/oc-intf:interface/oc-eth:ethernet/oc-eth:state/oc-lag:aggregate-id {
        deviate add {
            sonic-ext:field-transformer "intf_eth_aggr_id_xfmr";
        }
    }

    deviation /oc-intf:interfaces/oc-intf:interface/oc-eth:ethernet/oc-eth:state/oc-eth:duplex-mode {
        deviate add {
            sonic-ext:field-transformer "intf_eth_duplex_mode_xfmr";
        }
    }

    deviation /oc-intf:interfaces/oc-intf:interface/oc-eth:ethernet/oc-eth:state/oc-eth:mac-address {
        deviate add {
            sonic-ext:field-transformer "intf_eth_mac_address_xfmr";
        }
    }

    deviation /oc-intf:interfaces/oc-intf:interface/oc-eth:ethernet/oc-eth:state/oc-eth:negotiated-port-speed {
        deviate add {
            sonic-ext:field-transformer "intf_eth_negotiated_port_speed_xfmr";
        }
    }

    deviation /oc-intf:interfaces/oc-intf:interface/oc-eth:ethernet/oc-eth:state/google-pins-if:forwarding-viable {
        deviate add {
            sonic-ext:field-transformer "intf_eth_forwarding_viable_xfmr";
        }
    }

    deviation /oc-intf:interfaces/oc-intf:interface/oc-eth:ethernet/oc-eth:state/oc-eth:standalone-link-training {
        deviate add {
            sonic-ext:field-transformer "intf_eth_link_training_xfmr";
        }
    }

    deviation /oc-intf:interfaces/oc-intf:interface/oc-eth:ethernet/oc-eth:state/google-pins-if:transceiver-qualified {
        deviate add {
            sonic-ext:db-name "STATE_DB";
            sonic-ext:field-transformer "intf_eth_xcvr_qualified_xfmr";
        }
    }

    deviation /oc-intf:interfaces/oc-intf:interface/oc-eth:ethernet/oc-eth:state/google-pins-if:insert-ingress-timestamp {
        deviate add {
            sonic-ext:field-transformer "intf_eth_ingress_timestamp_xfmr";
        }
    }

    deviation /oc-intf:interfaces/oc-intf:interface/oc-eth:ethernet/oc-eth:state/google-pins-if:insert-egress-timestamp {
        deviate add {
            sonic-ext:field-transformer "intf_eth_egress_timestamp_xfmr";
        }
    }

    deviation /oc-intf:interfaces/oc-intf:interface/oc-intf:state {
        deviate add {
            sonic-ext:db-name "APPL_STATE_DB";
        }
    }

    deviation /oc-intf:interfaces/oc-intf:interface/oc-intf:config/oc-intf:mtu {
        deviate add {
            sonic-ext:field-transformer "intf_mtu_xfmr";
        }
    }

    deviation /oc-intf:interfaces/oc-intf:interface/oc-intf:state/oc-intf:mtu {
        deviate add {
            sonic-ext:field-transformer "intf_mtu_xfmr";
        }
    }

    deviation /oc-intf:interfaces/oc-intf:interface/oc-intf:state/oc-intf:admin-status {
        deviate add {
            sonic-ext:field-transformer "intf_admin_status_xfmr";
            sonic-ext:field-name "admin_status";
        }
    }

    deviation /oc-intf:interfaces/oc-intf:interface/oc-intf:config/oc-intf:enabled {
        deviate add {
            sonic-ext:field-transformer "intf_enabled_xfmr";
        }
    }

    deviation /oc-intf:interfaces/oc-intf:interface/oc-lag:aggregation/oc-lag:config/oc-lag:min-links {
        deviate add {
            sonic-ext:field-transformer "lag_min_links_xfmr";
        }
    }

    deviation /oc-intf:interfaces/oc-intf:interface/oc-lag:aggregation/oc-lag:config/oc-lag:lag-type {
        deviate add {
            sonic-ext:field-transformer "lag_type_xfmr";
        }
    }

    deviation /oc-intf:interfaces/oc-intf:interface/oc-lag:aggregation/oc-lag:state {
        deviate add {
            sonic-ext:subtree-transformer "intf_lag_state_xfmr";
            sonic-ext:path-transformer "intf_lag_state_xfmr";
        }
    }

    deviation /oc-intf:interfaces/oc-intf:interface/oc-lag:aggregation/oc-lag:state/oc-lag:lag-speed {
        deviate add {
            sonic-ext:composite-field-names "LAG_MEMBER_TABLE:link.speed,LAG_MEMBER_TABLE:runner.selected";
        }
    }

    deviation /oc-intf:interfaces/oc-intf:interface/oc-lag:aggregation/oc-lag:config/oc-lag:min-links {
        deviate add {
            sonic-ext:field-transformer "lag_min_links_xfmr";
            sonic-ext:field-name "min_links";
        }
    }

    deviation /oc-intf:interfaces/oc-intf:interface/oc-lag:aggregation/oc-lag:state {
      deviate add {
            sonic-ext:subtree-transformer "intf_lag_state_xfmr";
            sonic-ext:path-transformer "intf_lag_state_path_xfmr";
      }
    }

    deviation /oc-intf:interfaces/oc-intf:interface/oc-intf:state/oc-intf:enabled {
        deviate add {
            sonic-ext:field-transformer "intf_enabled_xfmr";
        }
    }

    deviation /oc-intf:interfaces/oc-intf:interface/oc-intf:state/oc-intf:counters {
        deviate add {
            sonic-ext:subtree-transformer "intf_get_counters_xfmr";
            sonic-ext:db-name "COUNTERS_DB";
        }
    }

    deviation /oc-intf:interfaces/oc-intf:interface/oc-eth:ethernet/oc-eth:state/oc-eth:counters {
        deviate add {
            sonic-ext:db-name "COUNTERS_DB";
            sonic-ext:subtree-transformer "intf_get_ether_counters_xfmr";
        }
    }

    deviation /oc-intf:interfaces {
        deviate add {
            sonic-ext:pre-transformer "intf_pre_xfmr";
            sonic-ext:post-transformer "intf_post_xfmr";
        }
    }

    deviation /oc-intf:interfaces/oc-intf:interface/oc-intf:config/oc-intf:name {
        deviate add {
            sonic-ext:field-transformer "intf_name_xfmr";
        }
    }

    deviation /oc-intf:interfaces/oc-intf:interface/oc-intf:config/google-pins-if:diag-profile {
        deviate add {
            sonic-ext:db-name "CONFIG_DB";
            sonic-ext:table-name "BLACKHOLE_PORT_TO_PROFILE_MAP";
            sonic-ext:field-transformer "intf_diag_profile_xfmr";
        }
    }

    deviation /oc-intf:interfaces/oc-intf:interface/oc-intf:state/google-pins-if:diag-profile {
        deviate add {
            sonic-ext:db-name "APPL_STATE_DB";
            sonic-ext:table-name "BLACKHOLE_PORT_TO_PROFILE_MAP";
            sonic-ext:field-transformer "intf_diag_profile_xfmr";
        }
    }

    deviation /oc-intf:interfaces/oc-intf:interface/oc-eth:ethernet/google-pins-if:pfc {
        deviate add {
            sonic-ext:db-name "COUNTERS_DB";
            sonic-ext:subtree-transformer "intf_eth_pfc_xfmr";
        }
    }

    deviation /oc-intf:interfaces/oc-intf:interface/oc-eth:ethernet/oc-eth:state/oc-eth:fec-mode {
        deviate add {
            sonic-ext:field-transformer "intf_eth_fec_mode_xfmr";
        }
    }

    deviation /oc-intf:interfaces/oc-intf:interface/oc-eth:ethernet/oc-eth:state/google-pins-if:sfec-mode {
        deviate add {
            sonic-ext:field-transformer "intf_eth_sfec_mode_xfmr";
        }
    }

    deviation /oc-intf:interfaces/oc-intf:interface/oc-eth:ethernet/oc-eth:state/google-pins-if:ingress-delay {
        deviate add {
            sonic-ext:db-name "APPL_STATE_DB";
            sonic-ext:field-transformer "intf_eth_ingress_delay_xfmr";
        }
    }

    deviation /oc-intf:interfaces/oc-intf:interface/oc-eth:ethernet/oc-eth:state/google-pins-if:egress-delay {
        deviate add {
            sonic-ext:db-name "APPL_STATE_DB";
            sonic-ext:field-transformer "intf_eth_egress_delay_xfmr";
        }
    }

    deviation /oc-intf:interfaces/oc-intf:interface/oc-eth:ethernet/oc-eth:state/google-pins-if:ingress-delay-applied {
        deviate add {
            sonic-ext:db-name "STATE_DB";
            sonic-ext:field-transformer "intf_eth_ingress_delay_applied_xfmr";
        }
    }

    deviation /oc-intf:interfaces/oc-intf:interface/oc-eth:ethernet/oc-eth:state/google-pins-if:egress-delay-applied {
        deviate add {
            sonic-ext:db-name "STATE_DB";
            sonic-ext:field-transformer "intf_eth_egress_delay_applied_xfmr";
        }
    }

    deviation /oc-intf:interfaces/oc-intf:interface/oc-eth:ethernet/oc-eth:state/google-pins-if:sfec-oper-mode {
        deviate add {
            sonic-ext:db-name "STATE_DB";
            sonic-ext:field-transformer "intf_eth_sfec_oper_mode_xfmr";
        }
    }

    deviation /oc-intf:interfaces/oc-intf:interface/oc-eth:ethernet/oc-eth:state/google-pins-if:enable-pfc-rx {
        deviate add {
            sonic-ext:field-transformer "intf_eth_state_pfc_enable_xfmr";
        }
    }

    deviation /oc-intf:interfaces/oc-intf:interface/oc-intf:state/oc-intf:loopback-mode {
        deviate add {
            sonic-ext:field-transformer "intf_loopback_mode_xfmr";
        }
    }

    deviation /oc-intf:interfaces/oc-intf:interface/oc-intf:config/oc-intf:loopback-mode {
        deviate add {
            sonic-ext:field-transformer "intf_loopback_mode_xfmr";
        }
    }

    deviation /oc-intf:interfaces/oc-intf:interface/oc-intf:state/oc-intf:type {
        deviate add {
            sonic-ext:field-transformer "intf_type_xfmr";
        }
    }

    deviation /oc-intf:interfaces/oc-intf:interface/oc-intf:config/oc-intf:type {
        deviate add {
            sonic-ext:field-transformer "intf_type_xfmr";
        }
    }

    deviation /oc-intf:interfaces/oc-intf:interface/oc-intf:config/google-pins-if:bridge-id {
        deviate add {
            sonic-ext:db-name "CONFIG_DB";
            sonic-ext:field-transformer "intf_bridge_id_xfmr";
        }
    }

    deviation /oc-intf:interfaces/oc-intf:interface/oc-intf:state/google-pins-if:bridge-id {
        deviate add {
            sonic-ext:db-name "APPL_STATE_DB";
            sonic-ext:field-transformer "intf_bridge_id_xfmr";
        }
    }

    deviation /oc-intf:interfaces/oc-intf:interface/oc-intf:config/pins-if:health-indicator {
        deviate add {
            sonic-ext:field-transformer "pins_if_health_indicator_xfmr";
        }
    }

    deviation /oc-intf:interfaces/oc-intf:interface/oc-intf:config/p4rt-if:id {
        deviate add {
            sonic-ext:field-transformer "pins_if_id_xfmr";
        }
    }

    deviation /oc-intf:interfaces/oc-intf:interface/oc-intf:state/oc-intf:ifindex {
        deviate add {
            sonic-ext:field-transformer "pins_ifindex_xfmr";
            sonic-ext:table-name "P4RT_PORT_ID_TABLE";
        }
    }

    deviation /oc-intf:interfaces/oc-intf:interface/oc-intf:state/oc-intf:management {
        deviate add {
            sonic-ext:field-transformer "intf_mgmt_xfmr";
        }
    }

    deviation /oc-intf:interfaces/oc-intf:interface/oc-intf:state/oc-intf:cpu {
        deviate add {
            sonic-ext:field-transformer "intf_cpu_xfmr";
        }
    }

    deviation /oc-intf:interfaces/oc-intf:interface/oc-intf:state/oc-intf:name {
        deviate add {
            sonic-ext:field-transformer "intf_name_xfmr";
        }
    }

    deviation /oc-intf:interfaces/oc-intf:interface/oc-intf:state/oc-plat-port:hardware-port {
        deviate add {
            sonic-ext:field-transformer "intf_hardware_port_xfmr";
            sonic-ext:field-name "index";
        }
    }

    deviation /oc-intf:interfaces/oc-intf:interface/oc-intf:state/oc-plat-xcvr:transceiver {
        deviate add {
            sonic-ext:field-transformer "intf_transceiver_xfmr";
        }
    }

    deviation /oc-intf:interfaces/oc-intf:interface/oc-intf:state/oc-plat-xcvr:physical-channel {
        deviate add {
            sonic-ext:field-transformer "intf_physical_channel_xfmr";
        }
    }

    deviation /oc-intf:interfaces/oc-intf:interface/oc-intf:state/oc-intf:last-change {
        deviate add {
            sonic-ext:field-transformer "intf_last_change_xfmr";
        }
    }

    deviation /oc-intf:interfaces/oc-intf:interface/oc-intf:state/pins-if:health-indicator {
        deviate add {
            sonic-ext:field-transformer "pins_if_health_indicator_xfmr";
            sonic-ext:field-name "health_indicator";
        }
    }

    deviation /oc-intf:interfaces/oc-intf:interface/oc-intf:state/p4rt-if:id {
        deviate add {
            sonic-ext:field-transformer "pins_if_id_xfmr";
            sonic-ext:table-name "P4RT_PORT_ID_TABLE";
        }
    }

    deviation /oc-intf:interfaces/oc-intf:interface/oc-intf:state/oc-intf:oper-status {
        deviate add {
            sonic-ext:field-transformer "intf_oper_status_xfmr";
            sonic-ext:composite-field-names "PORT_TABLE:oper_status,PORT_TABLE:presence,PORT_TABLE:loopback_mode,PORT_TABLE:under_test,MGMT_PORT_TABLE:oper_status,VLAN_TABLE:oper_status,LAG_TABLE:oper_status,LAG_TABLE:under_test,BRIDGE_TABLE:oper_status,INTF_TABLE:oper_status";
        }
    }

    deviation /oc-intf:interfaces/oc-intf:interface/oc-intf:state/oc-intf:description {
        deviate add {
            sonic-ext:field-transformer "intf_description_xfmr";
        }
    }

    deviation /oc-intf:interfaces/oc-intf:interface/oc-intf:config/google-pins-if:fully-qualified-interface-name {
        deviate add {
            sonic-ext:field-transformer "intf_fqin_xfmr";
        }
    }

    deviation /oc-intf:interfaces/oc-intf:interface/oc-intf:state/google-pins-if:fully-qualified-interface-name {
        deviate add {
            sonic-ext:field-transformer "intf_fqin_xfmr";
        }
    }

    deviation /oc-intf:interfaces/oc-intf:interface/oc-intf:config/google-pins-if:ecmp-hash-offset {
        deviate add {
            sonic-ext:field-transformer "intf_ecmp_hash_offset_xfmr";
            sonic-ext:db-name "CONFIG_DB";
        }
    }

    deviation /oc-intf:interfaces/oc-intf:interface/oc-intf:state/google-pins-if:ecmp-hash-offset {
        deviate add {
            sonic-ext:field-transformer "intf_ecmp_hash_offset_xfmr";
            sonic-ext:db-name "APPL_STATE_DB";
        }
    }

    deviation /oc-intf:interfaces/oc-intf:interface/oc-intf:config/google-pins-if:ecmp-hash-algorithm {
        deviate add {
            sonic-ext:field-transformer "intf_ecmp_hash_algorithm_xfmr";
            sonic-ext:table-name "PORT";
            sonic-ext:db-name "CONFIG_DB";
        }
    }

    deviation /oc-intf:interfaces/oc-intf:interface/oc-intf:state/google-pins-if:ecmp-hash-algorithm {
        deviate add {
            sonic-ext:field-transformer "intf_ecmp_hash_algorithm_xfmr";
            sonic-ext:table-name "PORT_TABLE";
            sonic-ext:db-name "APPL_STATE_DB";
        }
    }

    deviation /oc-intf:interfaces/oc-intf:interface/oc-intf:config/google-pins-if:port-direction {
        deviate add {
            sonic-ext:field-transformer "intf_port_direction_xfmr";
        }
    }

    deviation /oc-intf:interfaces/oc-intf:interface/oc-intf:state/google-pins-if:port-direction {
        deviate add {
            sonic-ext:field-transformer "intf_port_direction_xfmr";
            sonic-ext:db-name "APPL_STATE_DB";
        }
    }

    deviation /oc-intf:interfaces/oc-intf:interface/oc-intf:state/google-pins-if:blackhole {
        deviate add {
            sonic-ext:db-name "COUNTERS_DB";
            sonic-ext:subtree-transformer "intf_state_blackhole_xfmr";
        }
    }

    deviation /oc-intf:interfaces/oc-intf:interface/oc-intf:state/google-pins-if:hst {
        deviate add {
            sonic-ext:subtree-transformer "intf_state_hst_xfmr";
        }
    }

    deviation /oc-intf:interfaces/oc-intf:interface/oc-intf:hold-time/oc-intf:config {
        deviate add {
            sonic-ext:subtree-transformer "intf_hold_time_config_xfmr";
        }
    }

    deviation /oc-intf:interfaces/oc-intf:interface/oc-intf:hold-time/oc-intf:state {
        deviate add {
            sonic-ext:db-name "APPL_STATE_DB";
        }
    }

    deviation /oc-intf:interfaces/oc-intf:interface/oc-intf:hold-time/oc-intf:state/oc-intf:down {
        deviate add {
            sonic-ext:field-transformer "intf_hold_time_down_xfmr";
        }
    }

    deviation /oc-intf:interfaces/oc-intf:interface/oc-intf:hold-time/oc-intf:state/oc-intf:up {
        deviate add {
            sonic-ext:field-transformer "intf_hold_time_up_xfmr";
        }
    }

    deviation /oc-intf:interfaces/oc-intf:interface/oc-intf:subinterfaces {
        deviate add {
            sonic-ext:table-name "NONE";
        }
    }

    deviation /oc-intf:interfaces/oc-intf:interface/oc-intf:subinterfaces/oc-intf:subinterface {
        deviate add {
            sonic-ext:table-transformer "intf_subintfs_table_xfmr";
            sonic-ext:virtual-table "true";
            sonic-ext:key-transformer "intf_subintfs_xfmr";
            sonic-ext:path-transformer "intf_ip_path_xfmr";
        }
    }

    deviation /oc-intf:interfaces/oc-intf:interface/oc-intf:subinterfaces/oc-intf:subinterface/oc-intf:config/oc-intf:index {
        deviate add {
            sonic-ext:field-transformer "subif_index_xfmr";
            sonic-ext:table-name "NONE";
        }
    }

    deviation /oc-intf:interfaces/oc-intf:interface/oc-intf:subinterfaces/oc-intf:subinterface/oc-intf:state/oc-intf:index {
        deviate add {
            sonic-ext:field-transformer "subif_index_xfmr";
            sonic-ext:table-name "NONE";
        }
    }

    deviation /oc-intf:interfaces/oc-intf:interface/oc-intf:subinterfaces/oc-intf:subinterface/oc-ip:ipv4/oc-ip:addresses {
        deviate add {
            sonic-ext:table-name "NONE";
            sonic-ext:subtree-transformer "intf_ip_addr_xfmr";
        }
    }

    deviation /oc-intf:interfaces/oc-intf:interface/oc-intf:subinterfaces/oc-intf:subinterface/oc-ip:ipv6/oc-ip:addresses {
        deviate add {
            sonic-ext:table-name "NONE";
            sonic-ext:subtree-transformer "intf_ip_addr_xfmr";
        }
    }

    deviation /oc-intf:interfaces/oc-intf:interface/oc-intf:subinterfaces/oc-intf:subinterface/oc-ip:ipv4/oc-ip:addresses/oc-ip:address {
        deviate add {
            sonic-ext:key-transformer "subintf_ip_addr_key_xfmr";
        }
    }

    deviation /oc-intf:interfaces/oc-intf:interface/oc-intf:subinterfaces/oc-intf:subinterface/oc-ip:ipv6/oc-ip:addresses/oc-ip:address {
        deviate add {
            sonic-ext:key-transformer "subintf_ip_addr_key_xfmr";
        }
    }

    deviation /oc-intf:interfaces/oc-intf:interface/oc-intf:subinterfaces/oc-intf:subinterface/oc-ip:ipv4 {
        deviate add {
            sonic-ext:key-transformer "subintf_ipv4_tbl_key_xfmr";
            sonic-ext:table-transformer "intf_table_xfmr";
        }
    }

    deviation /oc-intf:interfaces/oc-intf:interface/oc-intf:subinterfaces/oc-intf:subinterface/oc-ip:ipv6 {
        deviate add {
            sonic-ext:key-transformer "subintf_ipv6_tbl_key_xfmr";
            sonic-ext:table-transformer "intf_table_xfmr";
        }
    }

    deviation /oc-intf:interfaces/oc-intf:interface/oc-intf:subinterfaces/oc-intf:subinterface/oc-ip:ipv6/oc-ip:config/oc-ip:enabled {
        deviate add {
            sonic-ext:field-transformer "ipv6_enabled_xfmr";
        }
    }

    deviation /oc-intf:interfaces/oc-intf:interface/oc-intf:subinterfaces/oc-intf:subinterface/oc-ip:ipv6/oc-ip:state/oc-ip:enabled {
        deviate add {
            sonic-ext:field-transformer "ipv6_enabled_xfmr";
        }
    }

    deviation /oc-intf:interfaces/oc-intf:interface/oc-intf:subinterfaces/oc-intf:subinterface/oc-ip:ipv4/oc-ip:config/oc-ip:enabled {
        deviate add {
            sonic-ext:field-transformer "ipv4_enabled_xfmr";
        }
    }

    deviation /oc-intf:interfaces/oc-intf:interface/oc-intf:subinterfaces/oc-intf:subinterface/oc-ip:ipv4/oc-ip:state/oc-ip:enabled {
        deviate add {
            sonic-ext:field-transformer "ipv4_enabled_xfmr";
        }
    }

    deviation /oc-intf:interfaces/oc-intf:interface/oc-intf:subinterfaces/oc-intf:subinterface/oc-intf:config/oc-intf:enabled {
        deviate add {
            sonic-ext:field-transformer "intf_enabled_xfmr";
        }
    }

    deviation /oc-intf:interfaces/oc-intf:interface/oc-intf:subinterfaces/oc-intf:subinterface/oc-intf:state/oc-intf:enabled {
        deviate add {
            sonic-ext:field-transformer "intf_enabled_xfmr";
        }
    }

    deviation /oc-intf:interfaces/oc-intf:interface/oc-intf:subinterfaces/oc-intf:subinterface/oc-ip:ipv4/oc-ip:state/oc-ip:counters {
        deviate add {
            sonic-ext:db-name "COUNTERS_DB";
            sonic-ext:subtree-transformer "intf_ipv4_counters_xfmr";
        }
    }

    deviation /oc-intf:interfaces/oc-intf:interface/oc-intf:subinterfaces/oc-intf:subinterface/oc-ip:ipv6/oc-ip:state/oc-ip:counters {
        deviate add {
            sonic-ext:db-name "COUNTERS_DB";
            sonic-ext:subtree-transformer "intf_ipv6_counters_xfmr";
        }
    }

    deviation /oc-intf:interfaces/oc-intf:interface/oc-intf:subinterfaces/oc-intf:subinterface/oc-ip:ipv6/oc-ip:unnumbered/oc-ip:config/oc-ip:enabled {
        deviate add {
            sonic-ext:field-transformer "unnumbered_enabled_xfmr";
        }
    }

    deviation /oc-intf:interfaces/oc-intf:interface/oc-intf:subinterfaces/oc-intf:subinterface/oc-ip:ipv6/oc-ip:unnumbered/oc-ip:state/oc-ip:enabled {
        deviate add {
            sonic-ext:field-transformer "unnumbered_enabled_xfmr";
        }
    }

    deviation "/oc-intf:interfaces/oc-intf:interface/oc-intf:state/google-pins-if:vendor-id" {
        deviate add {
            sonic-ext:db-name "APPL_STATE_DB";
            sonic-ext:field-transformer "intf_hw_vendor_id_xfmr";
            sonic-ext:field-name "hardware_vendor_id";
        }
    }

    deviation "/oc-intf:interfaces/oc-intf:interface/oc-intf:state/google-pins-if:encoded-id" {
        deviate add {
            sonic-ext:field-transformer "intf_encoded_id_xfmr";
        }
    }

    deviation "/oc-intf:interfaces/oc-intf:interface/oc-intf:config/google-pins-if:encoded-id" {
        deviate add {
            sonic-ext:field-transformer "intf_encoded_id_xfmr";
        }
    }

    deviation "/oc-intf:interfaces/oc-intf:interface/oc-intf:penalty-based-aied" {
        deviate add {
            sonic-ext:subtree-transformer "intf_aied_link_damping_xfmr";
        }
    }
}
