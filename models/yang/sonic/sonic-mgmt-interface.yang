module sonic-mgmt-interface {
    namespace "http://github.com/Azure/sonic-mgmt-interface";
    prefix smgmtint;

    import ietf-inet-types {
        prefix inet;
    }

    import sonic-mgmt-port {
        prefix mgmtprt;
    }

    organization
        "SONiC";

    contact
        "SONiC";

    description
        "SONiC MANAGEMENT INTERFACE";

    revision 2019-11-13 {
        description
            "Initial revision.";
    }

    typedef ip-family {
        type enumeration {
            enum IPv4;
            enum IPv6;
        }
    }

    container sonic-mgmt-interface {

        container MGMT_INTERFACE {

            list MGMT_INTERFACE_LIST {

                key "portname";

                leaf portname{
                    type leafref {
                        path "/mgmtprt:sonic-mgmt-port/mgmtprt:MGMT_PORT/mgmtprt:MGMT_PORT_LIST/mgmtprt:ifname";
                    }
                }

            }

            list MGMT_INTERFACE_IPADDR_LIST {

                key "portname ip_prefix";

                leaf portname{
                    type leafref {
                        path "/mgmtprt:sonic-mgmt-port/mgmtprt:MGMT_PORT/mgmtprt:MGMT_PORT_LIST/mgmtprt:ifname";
                    }
                }

                leaf ip_prefix {
                    type inet:ip-prefix;
                }

                leaf family {

                    /* family leaf needed for backward compatibility
                       Both ip4 and ip6 address are string in IETF RFC 6021,
                       so must statement can check based on : or ., family
                       should be IPv4 or IPv6 according.
                     */

                    must "(contains(../ip_prefix, ':') and current()='IPv6') or
                      (contains(../ip_prefix, '.') and current()='IPv4')";
                    type ip-family;
                }

            }

        }

        container MGMT_INTF_TABLE {
            config false;

            list MGMT_INTF_TABLE_LIST {
                key "ifName";

                leaf ifName {
                    type string;
                }
            }

            list MGMT_INTF_TABLE_IPADDR_LIST {
                key "ifName ipPrefix";

                leaf ifName {
                   type string;
                }

                leaf ipPrefix {
                    type inet:ip-prefix;
                }
             }
        }

    }

}
