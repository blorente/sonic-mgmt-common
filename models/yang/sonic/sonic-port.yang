module sonic-port {
    namespace "http://github.com/Azure/sonic-port";
    prefix prt;
    yang-version 1.1;

    import ietf-yang-types {
        prefix yang;
    }

    import sonic-common {
        prefix scommon;
    }

    import sonic-extension {
        prefix sonic-ext;
    }

    organization
        "SONiC";

    contact
        "SONiC";

    description
        "SONIC PORT";

    revision 2024-02-06 {
        description
            "Use enum type for loopback-mode";
    }

    revision 2023-02-27 {
        description
            "Added port-direction field";
    }

    revision 2020-08-04 {
        description
            "Added fec attribute";
    }

    revision 2019-05-15 {
        description
            "Initial revision.";
    }

    typedef fec-mode {
        type enumeration {
            enum FEC_DISABLED;
            enum FEC_FC;
            enum FEC_RS528;
            enum FEC_RS544;
            enum FEC_RS544_2X_INTERLEAVE;
        }
    }

    typedef loopback-mode-type {
        type enumeration {
            enum none;
            enum mac_local;
            enum mac_remote;
            enum phy_local;
            enum phy_remote;
        }
    }

    typedef link-event-damping-algorithm {
        type enumeration {
            enum disabled;
            enum aied;
        }
    }

    typedef learn-mode-type {
        type enumeration {
            enum disable;
        }
    }


    container sonic-port {

        container PORT {

            list PORT_LIST {
                key "ifname";
                    sonic-ext:custom-validation ValidateDpbStatus;

                leaf ifname {
                    type string {
                        pattern "(^Ethernet.*)" {
                            error-message "Invalid interface name";
                            error-app-tag interface-name-invalid;
                        }
                    }
                }

                leaf index {
                    type uint16;
                }

                leaf speed {
                    type uint64;
                }

                leaf adv_speeds {
                    type uint64;
                }

                leaf valid_speeds {
					type string;
				}

                leaf fec {
                    type scommon:fec-mode;
                }

                leaf adv_extended_fec_modes {
                    type scommon:fec-mode;
                }

                leaf fec-mode {
                    type fec-mode;
                }

                leaf sfec_mode {
                    type string;
                }

                leaf alias {
                    type string;
                }

                leaf description {
                    type string;
                }
                leaf autoneg {
                        type string;
                }

                leaf mtu{
                    type uint32 {
                        range "1312..9216" {
                            error-message "Invalid MTU value";
                            error-app-tag mtu-invalid;
                        }
                    }
                }

                leaf health_indicator {
                    type scommon:health-indicator;
                }

                leaf id {
                    type uint32;
                }

                leaf hold_time_up {
                    type uint32;
                }

                leaf hold_time_down {
                    type uint32;
                }

                leaf lanes {
                    type string;
                }

                leaf admin_status {
                    type scommon:admin-status;
                }

                leaf loopback-mode {
                    type loopback-mode-type;
                    default none;
                }

                leaf duplex-mode {
                    type scommon:duplex-mode;
                    default full;
                }
                leaf mac-address {
                    type yang:mac-address;
                }

                leaf forwarding-viable {
                    type boolean;
                    default true;
                }

                leaf pfc_asym {
                    type string {
                        pattern "on|off";
                    }
                }

                leaf fully-qualified-interface-name {
                    type string;
                }

                leaf link_training {
                    type string;
                    default "0";
                }

                leaf ecmp_hash_offset {
                    type uint8 {
                        range "0..15" {
                            error-message "Invalid ECMP hash offset; should be between 0-15";
                        }
                    }
                    description
                        "The offset used when calculating the hash algorithm";
                }

                leaf ecmp_hash_algorithm {
                    type string;
                    default "crc";
                }

                leaf ecmp_hash_seed {
                    type uint32;
                    description
                        "The seed used to initialize the hash algorithm";
                }

                leaf port_direction {
                    type string;
                    description
                        "Describes whether the port is host-facing, fabric-facing, or another direction";
                }

                leaf ingress-delay {
                    type string;
                }

                leaf egress-delay {
                    type string;
                }

                leaf encoded_id {
                    type uint32;
                }

                leaf ingress_timestamp_enable {
                    type boolean;
                }

                leaf egress_timestamp_enable {
                    type boolean;
                }

                leaf max_suppress_time {
                    type uint32;
                }

                leaf decay_half_life {
                    type uint32;
                }

                leaf suppress_threshold {
                    type uint32;
                }

                leaf reuse_threshold {
                    type uint32;
                }

                leaf flap_penalty {
                    type uint32;
                }

                leaf link_event_damping_algorithm {
                    type link-event-damping-algorithm;
                    default disabled;
                }

                leaf learn_mode {
                    type learn-mode-type;
                    default disable;
                }
            }
        }
        container PORT_TABLE {
            config false;

            list PORT_TABLE_LIST {
                key "ifname";

                leaf ifname {
                    type union {
                        type leafref {
                            path "/prt:sonic-port/prt:PORT/prt:PORT_LIST/prt:ifname";
                        }
                        type string {
                            pattern "CPU";
                        }
                    }
                }

                leaf index {
                    type uint16;
                }

                leaf lanes {
                    type string;
                }

                leaf mtu {
                    type uint32 {
                        range "1312..9216" {
                            error-message "Invalid MTU value";
                            error-app-tag mtu-invalid;
                        }
                    }
                }

                leaf alias {
                    type string;
                }

                leaf oper_status {
                    type scommon:oper-status;
                }

                leaf admin_status {
                    type scommon:admin-status;
                }

                leaf health_indicator {
                    type scommon:health-indicator;
                }

                leaf id {
                    type uint32;
                }

                leaf hold_time_up {
                    type uint32;
                }

                leaf hold_time_down {
                    type uint32;
                }

                leaf description {
                    type string;
                }

                leaf speed {
                    type uint64;
                }

                leaf fec {
                    type scommon:fec-mode;
                }

                leaf fec-mode {
                    type fec-mode;
                }

                leaf sfec_mode {
                    type string;
                }

                leaf pfc_asym {
                    type string {
                        pattern "on|off";
                    }
                }

                leaf autoneg {
                    type boolean;
                    default false;
                }
                leaf loopback-mode {
                    type loopback-mode-type;
                    default none;
                }
                leaf duplex-mode {
                    type scommon:duplex-mode;
                    default full;
                }
                leaf mac-address {
                    type yang:mac-address;
                }
                leaf negotiated-port-speed {
                    type uint64;
                }
                leaf forwarding-viable {
                    type boolean;
                    default true;
                }
                leaf hardware-port {
                    type string;
                }
                leaf fully-qualified-interface-name {
                    type string;
                }
                leaf link_training {
                        type string;
                        default "0";
                }
                leaf encoded_id {
                    type uint32;
                }

                leaf ingress_timestamp_enable {
                    type boolean;
                }

                leaf egress_timestamp_enable {
                    type boolean;
                }

                leaf max_suppress_time {
                    type uint32;
                }

                leaf decay_half_life {
                    type uint32;
                }

                leaf suppress_threshold {
                    type uint32;
                }

                leaf reuse_threshold {
                    type uint32;
                }

                leaf flap_penalty {
                    type uint32;
                }

                leaf link_event_damping_algorithm {
                    type link-event-damping-algorithm;
                    default disabled;
                }

                leaf learn_mode {
                    type learn-mode-type;
                    default disable;
                }
            }
        }
        container CPU_PORT {

            list CPU_PORT_LIST {
                key "ifname";

                leaf ifname {
                    type string {
                        pattern "CPU" {
                            error-message "Invalid interface name";
                            error-app-tag interface-name-invalid;
                        }
                    }
                }

                leaf id {
                    type uint32;
                }
            }
        }
    }
}
