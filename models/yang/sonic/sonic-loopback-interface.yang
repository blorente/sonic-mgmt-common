module sonic-loopback-interface {
    namespace "http://github.com/Azure/sonic-loopback-interface";
    prefix sonic-lo-if;
    yang-version 1.1;

    import ietf-inet-types {
        prefix inet;
    }

    import sonic-loopback {
        prefix lp;
    }

    organization
        "SONiC";

    contact
        "SONiC";

    description
        "SONIC LOOPBACK INTERFACE";

    revision 2019-07-02 {
        description
            "Initial revision.";
    }

    container sonic-loopback-interface {

        container LOOPBACK_INTERFACE {

            list LOOPBACK_INTERFACE_LIST {
                key "loIfName";

                leaf loIfName {
                    type leafref {
                        path "/lp:sonic-loopback/lp:LOOPBACK/lp:LOOPBACK_LIST/lp:name";
                    }
                }
            }

            list LOOPBACK_INTERFACE_IPADDR_LIST {
                key "loIfName ip_prefix";

                leaf loIfName{
                    type string;
                }

                leaf ip_prefix {
                    type inet:ip-prefix;

                }
            }
        }
    }
}
