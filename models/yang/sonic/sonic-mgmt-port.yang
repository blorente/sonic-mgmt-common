module sonic-mgmt-port {
    namespace "http://github.com/Azure/sonic-mgmt-port";
    prefix smgmtprt;

    import sonic-common {
        prefix scommon;
    }

    organization
        "SONiC";

    contact
        "SONiC";

    description
        "SONiC Management Interface";

    revision 2019-11-13 {
        description
            "Initial revision.";
    }


    container sonic-mgmt-port {

        container MGMT_PORT {

            list MGMT_PORT_LIST {

                key "ifname";

                leaf ifname {
                    type string {
                        pattern "(eth|bond)([1-3][0-9]{3}|[1-9][0-9]{2}|[1-9][0-9]|[0-9])"{
                            error-message "Invalid Management interface name";
                            error-app-tag mgmt-interface-name-invalid;
                        }
                    }
                }

                leaf speed {
                    type uint64 {
                        range "10|100|1000" {
                            error-message "Invalid Management interface speed";
                            error-app-tag mgmt-speed-invalid;
                        }
                    }
                }

                leaf autoneg {
                    type boolean;
                    default true;
                }

                leaf alias {
                    type string;
                }

                leaf description {
                    type string;
                }

                leaf mtu{
                    type uint32 {
                        range "1500..9216" {
                            error-message "Invalid Management interface MTU value";
                            error-app-tag mgmt-mtu-invalid;
                        }
                    }
                    default 1500;
                }

                leaf admin_status {
                    type scommon:admin-status;
                    default up;
                }

            }

        }

    }

}
