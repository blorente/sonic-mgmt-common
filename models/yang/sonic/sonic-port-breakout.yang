module sonic-port-breakout {
    namespace "http://github.com/Azure/sonic-port-breakout";
    prefix sbrkprt;

    import sonic-port {
        prefix prt;
    }

    import sonic-extension {
        prefix sonic-ext;
    }

    organization
        "SONiC";

    contact
        "SONiC";

    description
        "SONiC Port Breakout";

    revision 2020-03-12 {
        description
            "Initial revision.";
    }

    container sonic-port-breakout {

        container BREAKOUT_CFG {

            list BREAKOUT_CFG_LIST {

                key "ifname";

                leaf ifname {
                    description
                        "A port's primary interface name (which is used to store
                        breakout information for the entire port).
                        This port does not necessarily need to be realized/setup
                        (ie: no corresponding PORT entry)";
                    type string {
                        pattern "(^Ethernet.*)";
                    }
                }

                leaf port {
                    type string;
                }

                leaf brkout_mode {
                    type enumeration {
                        enum 1x400G { value 1; }
                        enum 1x100G { value 2; }
                        enum 1x40G { value 3; }
                        enum 2x100G { value 4; }
                        enum 2x50G { value 5; }
                        enum 4x25G { value 6; }
                        enum 4x10G { value 7; }
                        enum 2x200G { value 8; }
                        enum 4x100G { value 9; }
                        enum 4x50G { value 10; }
                        // Format for mixed speeds below as per SONiC HLD syntax:
                        // E.g 2x100G4_1x200G4 is translated as number1xspeed1numberA_number2xspeedXnumberB
                        // indicates numberA (4)  of lanes were used for number1 (2) of port(s) with default speed1 (100G).
                        // Same thing for number2, speedX, and numberB and so on.

                        // TODO(b/188458954): Ideally, we should have modes: 2x100G(4)+1x200G(4), 1x200G(4)+1x100G(4), etc.
                        // Lexer cannot process `(`, `)` in enum.
                        // For the time being, omitting `(`, and `)`, and replacing `+` with `_`.
                        // We might want to revisit this.
                        enum 2x100G4_1x200G4 { value 11; }
                        enum 1x200G4_2x100G4 { value 12; }
                        enum 1x400G4_2x200G4 { value 13; }
                        enum 2x200G4_1x400G4 { value 14; }
                        enum 2x400G { value 15; }
                        enum 4x200G { value 16; }
                        enum 1x400G4_1x100G4 { value 17; }
                        enum 1x100G4_1x400G4 { value 18; }
                        enum 1x400G4_1x200G4 { value 19; }
                        enum 1x200G4_1x400G4 { value 20; }
                        enum 1x200G4_1x100G4 { value 21; }
                        enum 1x100G4_1x200G4 { value 22; }
                        enum 2x40G { value 23; }
                        enum 1x200G4_1x40G4 { value 24; }
                        enum 1x40G4_1x200G4 { value 25; }
                        enum 1x100G4_1x40G4 { value 26; }
                        enum 1x40G4_1x100G4 { value 27; }
                        enum 8x100G { value 28; }
                        enum 1x100G4_2x100G4 { value 29; }
                        enum 2x100G4_1x100G4 { value 30; }
                        enum 8x10G { value 31; }
                        enum 8x25G { value 32; }
                        enum 8x50G { value 33; }
                        enum 2x50G4_1x200G4 { value 34; }
                        enum 1x200G4_2x50G4 { value 35; }
                        enum 1x100G4_4x10G4 { value 36; }
                        enum 4x10G4_1x100G4 { value 37; }
                        enum 1x400G4_2x50G4 { value 38; }
                        enum 2x50G4_1x400G4 { value 39; }
                    }
                }
                leaf lanes {
                    type string;
                }
                leaf name {
                    type string {
                        pattern "1/([1-3][0-9]{3}|[1-9][0-9]{2}|[1-9][0-9]|[0-9])";
                    }
                }
                leaf port-id {
                    type uint32;
                }
            }
        }

        container BREAKOUT_PORTS {

            list BREAKOUT_PORTS_LIST {

                key "ifname";

                leaf ifname {
                    type string {
                        pattern "(^Ethernet.*)";
                    }
                }

                leaf master {
                    type string;
                }
            }
        }

        container PORT_STATE {

            list PORT_STATE_LIST {

                key "ifname";

                leaf ifname {
                    type string {
                        pattern "(^Ethernet.*)";
                    }
                }

                leaf phase {
                    type string;
                }

                leaf timestamp {
                    type string;
                }
            }
        }

        container PORT_UNLOCK {

            list PORT_UNLOCK_LIST {

                key "ifname";

                leaf ifname {
                    type string {
                        pattern "(^Ethernet.*)";
                    }
                }
            }
        }

        container BREAKOUT_PORT_XCVR_CFG {

            list BREAKOUT_PORT_XCVR_CFG_LIST {

                key "portname ifname";

                leaf portname {
                    type string {
                        pattern "1/([1-3][0-9]{3}|[1-9][0-9]{2}|[1-9][0-9]|[0-9])";
                    }
                }
                leaf ifname {
                    type string {
                        pattern "(^Ethernet.*)";
                    }
                }
            }
        }

        container PORT_BREAKOUT {
            sonic-ext:db-name "STATE_DB";
            sonic-ext:key-delim "|";
            config false;
            list PORT_BREAKOUT_LIST {
                key "ifname";
                leaf ifname {
                    type string {
                        pattern "(^Ethernet.*)";
                    }
                }

                leaf status {
                    type string;
                }

                leaf name {
                    type string {
                        pattern "1/([1-3][0-9]{3}|[1-9][0-9]{2}|[1-9][0-9]|[0-9])";
                    }
                }

                leaf parent {
                    type string;
                }
                leaf port-id {
                    type uint32;
                }
            }
        }
    }

    rpc breakout_dependencies {

        description "RPC for showing dependencies on breakout port
        input is Ethernet interface";

        input {
            leaf ifname {
                type leafref {
                    path "/prt:sonic-port/prt:PORT/prt:PORT_LIST/prt:ifname";
                }
            }
        }

        output {
            leaf-list keys {
                type string;
                description
                    "On success, returns list of dependent table keys";
            }
        }
    }

    rpc breakout_capabilities {

        description "RPC for listing the breakout capabilities of ports
        input is Ethernet interface";

        input {
            leaf ifname {
                type leafref {
                    path "/prt:sonic-port/prt:PORT/prt:PORT_LIST/prt:ifname";
                }
            }
        }

        output {
            list caps {
                leaf port {
                    type string;
                }
                leaf modes {
                    type string;
                }
                leaf defmode {
                    type string;
                }
            }
        }
    }
}
