module sonic-interface {
    	namespace "http://github.com/Azure/sonic-interface";
	prefix sint;

	import ietf-inet-types {
		prefix inet;
	}

	import sonic-port {
		prefix prt;
	}

    import sonic-common {
        prefix cmn;
    }

	organization
		"SONiC";

	contact
		"SONiC";

	description
		"SONIC INTERFACE";

	revision 2024-05-29 {
        description
            "Add unnumbered_enabled field.";
    }
    revision 2019-07-02 {
		description
			"Initial revision.";
	}

	container sonic-interface {

		container INTERFACE {

			list INTERFACE_LIST {
				key "portname";

				leaf portname{
					type leafref {
						path "/prt:sonic-port/prt:PORT/prt:PORT_LIST/prt:ifname";
					}
				}

				/* Add a leafref, once VRF YANG is supported 
				leaf vrf-name {
					type string {
						pattern 'Vrf([-a-zA-Z0-9_]{1,60})' {
							error-app-tag vrf-name-invalid;
						}
					}
				}
				*/

                leaf unnumbered_enabled {
                    must "((/cmn:operation/cmn:operation != 'CREATE') and (/cmn:operation/cmn:operation != 'UPDATE')) or " +
                         "not(contains(/sonic-interface/INTERFACE/INTERFACE_IPADDR_LIST[portname=current()/../portname]/ip_prefix, '.'))"
                    {
                        error-message "Cannot configure IP address and IP Unnumbered interface configurations on the same interface";
                        error-app-tag intf-ip-config;
                    }
                    type boolean;
                }

			}

			list INTERFACE_IPADDR_LIST {
				key "portname ip_prefix";

				leaf portname{
					type leafref {
						path "/prt:sonic-port/prt:PORT/prt:PORT_LIST/prt:ifname";
					}
				}

				leaf ip_prefix {
					type inet:ip-prefix;
				}
			}
		}
	}
}
