module google-pins-platform {
  yang-version "1";

  // namespace
  namespace "http://openconfig.net/yang/google/platform";
  prefix "google-pins-platform";

  // import some basic types
  import openconfig-extensions { prefix oc-ext; }
  import openconfig-pins-platform-chassis { prefix oc-pins-platform-chassis; }
  import openconfig-platform { prefix oc-platform; }
  import openconfig-platform-types { prefix oc-platform-types; }
  import openconfig-platform-transceiver { prefix oc-transceiver; }
  import openconfig-types { prefix oc-types; }
  import openconfig-yang-types { prefix oc-yang; }

  // meta
  organization
      "Google Openconfig Working Group";

  contact
      "openconfig-dev@google.com";

  description
    "Google Specific extensions to OpenConfig Platform model.";

  oc-ext:openconfig-version "0.21.0";

  revision 2024-11-27 {
    description
      "Add SWITCH3 platform type.";
    reference "0.21.0";
  }

  revision 2024-09-20 {
    description
      "Add additional SSD leaves.";
    reference "0.20.0";
  }

  revision 2024-08-21 {
    description
      "Remove chassis/state/model-name.";
    reference "0.19.0";
  }


  revision 2024-08-20 {
    description
      "Add the peak-power-interval leaf to rails/rail/state/.";
    reference "0.18.0";
  }

  revision 2024-04-11 {
    description
      "Adds switch level diag counters to integrated-circuit.";
    reference "0.17.0";
  }

  revision 2024-03-25 {
    description
      "Adds ALPINEVS platform.";
    reference "0.16.0";
  }

  revision 2023-08-01 {
    description
      "Adds FANTRAY component.";
    reference "0.15.0";
  }

  revision 2023-02-16 {
    description
      "Added SSD leaves.";
    reference "0.14.0";
  }

  revision 2022-12-13 {
    description
      "Added reset-count leaf to fpga.";
    reference "0.13.0";
  }

  revision 2022-07-01 {
    description
      "Updates the power-supply subtree definition.";
    reference "0.12.0";
  }

  revision 2022-02-09 {
    description
      "Add the speed-control-pct path.";
    reference "0.11.0";
  }

  revision 2022-01-18 {
    description
      "Adding high and low threshold values for temperature and input/output
      power.";
    reference "0.10.0";
  }

  revision 2021-12-06 {
    description
      "Adding count of io-errors to storage component.";
    reference "0.9.0";
  }

  revision 2021-10-13 {
    description
      "Adding state leaves to Hardware Security Module.";
    reference "0.8.0";
  }

  revision 2021-09-05 {
    description
      "Adding state leaves to PSU component.";
    reference "0.7.0";
  }

  revision 2021-08-27 {
    description
      "Adding fpga component.";
    reference "0.6.0";
  }

  revision 2021-08-05 {
    description
      "Adding maximum speed to the fan component.";
    reference "0.5.0";
  }

  revision 2021-08-03 {
    description
      "Adding identities for boot-loader types and adding
      boot-loader container under component.";
    reference "0.4.0";
  }

  revision 2021-07-30 {
    description
      "Adding identities for sensor types and adding
      sensor container under component.";
    reference "0.3.0";
  }

  revision 2021-07-21 {
    description
      "Adding model-name to chassis component state and
      latest-available-firmware-version to transceiver
      component state.";
    reference "0.2.0";
  }

  revision 2021-01-26 {
    description
      "Initial version.";
    reference "0.1.0";
  }

  // identity statements
  identity HARDWARE_SECURITY_MODULE {
    base oc-platform-types:OPENCONFIG_HARDWARE_COMPONENT;
    description
      "Component that represents a Hardware Security Module.";
  }

  identity POWER_SUPPLY_TYPE {
    description
      "Base identity for power supply component sub-types.";
  }

  identity POWER_SEQUENCER {
    base POWER_SUPPLY_TYPE;
    description
      "Power supply component that can monitor and sequence multiple
      power-supply voltage inputs. It is PMBus/I2C addressable.";
  }

  identity POWER_BRICK {
    base POWER_SUPPLY_TYPE;
    description
      "Power supply component that plugs into the device via a cord and
      to the mains suppoy via another cord. It is similar in shape and
      weight to a brick.";
  }

  identity POWER_VOLTAGE_REGULATOR {
    base POWER_SUPPLY_TYPE;
    description
      "Power supply component that is designed to automatically maintain
      a constant voltage. It may use a simple feed-forward design or may
      include negative feedback.";
  }

  identity POWER_HOTSWAP {
    base POWER_SUPPLY_TYPE;
    description
      "Power supply component that allows a circuit board to be removed
      from or inserted into a live backplane.";
  }

  // identity statements
  identity SENSOR_TYPE {
    description
      "Base identity for sensor types.";
  }

  identity DIMM_TEMPERATURE_SENSOR {
    base SENSOR_TYPE;
    description
      "Sensor that measures temperature of dual inline memory module (DRAM).";
  }

  identity INLET_TEMPERATURE_SENSOR {
    base SENSOR_TYPE;
    description
      "Inlet temperature sensor on the chassis.";
  }

  identity HEAT_SINK_TEMPERATURE_SENSOR {
    base SENSOR_TYPE;
    description
      "Heat sink temperature sensor on the chassis.";
  }

  identity EXHAUST_TEMPERATURE_SENSOR {
    base SENSOR_TYPE;
    description
      "Exhaust temperature sensor on the chassis.";
  }

  identity SWITCH3 {
    base oc-pins-platform-chassis:PLATFORM_TYPE;
    description
      "Switch3 platform. See go/switch3 for more details.";
  }

  identity SWITCH1 {
    base oc-pins-platform-chassis:PLATFORM_TYPE;
    description
      "Switch1 platform. See go/switch1 for more details.";
  }

  identity TORSWITCH {
    base oc-pins-platform-chassis:PLATFORM_TYPE;
    description
      "Torswitch platform. See go/torswitch for more details.";
  }

  identity SWITCH4 {
    base oc-pins-platform-chassis:PLATFORM_TYPE;
    description
      "Mako Shark platform. See go/switch4 for more details.";
  }

  identity SWITCH2 {
    base oc-pins-platform-chassis:PLATFORM_TYPE;
    description
      "Switch2 platform. See go/switch2 for more details.";
  }

  identity ALPINEVS {
    base oc-pins-platform-chassis:PLATFORM_TYPE;
    description
      "Alpine VS platform. See go/gpins-alpine for more details.";
  }

  identity BOOT_LOADER_TYPE {
    description
      "Base identity for bootloader types.";
  }

  identity COREBOOT_NERF {
    base BOOT_LOADER_TYPE;
    description
      "NERF is responsible for downloading netboot images and/or securely
      booting the mission mode software.";
  }

  identity NETLO {
    base BOOT_LOADER_TYPE;
    description
      "Netlo allows for the loading of the running image from a remote
      source through the in-band interface.";
  }

  identity UBOOT {
    base BOOT_LOADER_TYPE;
    description
      "The Universal Boot Loader is responsible for:
       1. Netboot in out-of-band switches
       2. Loading the desired kernel image.";
  }

  identity FPGA {
    base oc-platform-types:OPENCONFIG_HARDWARE_COMPONENT;
    description
      "A field-programmable gate array is an integrated circuit designed
      to be configured by a customer or a designer after manufacturing,
      hence the term field-programmable. go/go/switch1-hw-spec has more
      details on the use of FPGAs in Switch1 chassis.";
  }

  identity FANTRAY {
    base oc-platform-types:OPENCONFIG_HARDWARE_COMPONENT;
    description
      "Component to house multiple cooling fans";
  }

  // grouping statements
  grouping google-pins-platform-state {
    description
      "Google specific state for platform components.";

    leaf storage-side {
      type enumeration {
        enum SIDE_A {
          description
            "Side A of the SD Card/SSD in which the software is stored.";
        }
        enum SIDE_B {
          description
            "Side B of the SD Card/SSD in which the software is stored.";
        }
      }
      description
        "Location of the software component within the system; side a or b.";
    }
  }

  grouping google-pins-transceiver-state {
    description
      "Google specific state for transceiver component.";

    leaf latest-available-firmware-version {
      type string;
      description
        "Latest available firmware image version for the transceiver.";
    }
  }

  grouping google-pins-transceiver-power-state {
    description
      "Google specific power state for transceiver component.";

    leaf low-warn-threshold {
      type decimal64 {
        fraction-digits 1;
      }
      units dBm;
      description
        "The threshold for power below which an alarm with severity warning
        may be raised.";
    }

    leaf low-critical-threshold {
      type decimal64 {
        fraction-digits 1;
      }
      units dBm;
      description
        "The threshold for power below which an alarm with severity critical
        may be raised.";
    }

    leaf high-warn-threshold {
      type decimal64 {
        fraction-digits 1;
      }
      units dBm;
      description
        "The threshold for power above which an alarm with severity warning
        may be raised.";
    }

    leaf high-critical-threshold {
      type decimal64 {
        fraction-digits 1;
      }
      units dBm;
      description
        "The threshold for power above which an alarm with severity critical
        may be raised.";
    }
  }

  grouping google-pins-fan-state {
    description
      "Google specific state for fan component.";

    leaf max-speed {
      type uint32;
      units rpm;
      description
        "Maximum fan speed.";
    }

    leaf speed-control-pct {
      type uint32;
      units percent;
      description
        "Intent of the fan control module (pwm) in the switch expressed as a
        percentage of max.";
    }
  }

  grouping google-pins-fpga {
    description
      "Top level grouping for the fpga component.";

    container fpga {
      description
        "Google specific augments for the fpga component.";

      container config {
        description
          "Configuration data for the fpga component.";
      }

      container state {
        config false;
        description
          "Operational state data for the fpga component.";

        leaf reset-count {
          type uint8;
          description "Number of resets.";
        }
      }

      uses google-pins-fpga-reset-causes;
    }
  }

  grouping google-pins-power-supply-rails-state {
    description
      "Grouping for operational state of a power supply component's power
       rail.";

    leaf name {
      type string;
      description
        "The name of the power rail.";
    }
    leaf direction {
      type enumeration {
        enum INPUT {
          description
            "The power rail is an input to the power supply component.";
        }
        enum OUTPUT {
          description
            "The power rail is an output of the power supply component.";
        }
      }
      description
        "The direction of the power rail.";
    }
    leaf status-vout {
      type oc-types:ieeefloat32;
      units volts;
      description
        "Maps to STATUS_VOUT in PMBUS standard.";
    }
    leaf commanded-voltage {
      type oc-types:ieeefloat32;
      units volts;
      description
        "Maps to VOUT_COMMAND in PMBUS standard.";
    }
    leaf energy {
      type oc-types:ieeefloat32;
      units joules;
      description
        "Maps to READ_EIN in PMBUS standard.";
    }
    leaf current {
      type oc-types:ieeefloat32;
      units amps;
      description
        "Maps to READ_IIN / READ_IOUT in PMBUS standard.";
    }
    leaf voltage {
      type oc-types:ieeefloat32;
      units volts;
      description
        "Maps to READ_VIN or READ_VOUT in PMBUS standard.";
    }
    leaf power {
      type oc-types:ieeefloat32;
      units watts;
      description
        "Maps to READ_PIN in PMBUS standard.";
    }
    leaf peak-power {
      type oc-types:ieeefloat32;
      units watts;
      description
        "Maps to PEAK_PIN in PMBUS standard.";
    }
    leaf peak-power-interval {
      type uint64;
      units nanoseconds;
      description
        "The time interval over which peak-power is measured. A
        value of zero indicates an absolute peak value (i.e. it
        is not periodically reset).";
    }
    leaf peak-voltage {
      type oc-types:ieeefloat32;
      units volts;
      description
        "Maps to PEAK_VIN or PEAK_VOUT in PMBUS standard.";
    }
    leaf peak-current {
      type oc-types:ieeefloat32;
      units amps;
      description
        "Peak current of the voltage rail. Maps to PEAK_IOUT in PMBUS
         standard.";
    }
    leaf temperature {
      type decimal64 {
        fraction-digits 1;
      }
      units celcius;
      description
        "Maps to READ_TEMPERATURE_N in PMBUS standard.";
    }
  }

  grouping google-pins-power-supply-rails-top {
    description
      "Top level grouping for all rails of a power supply component.";

    container rails {
      description
        "Operational state data of each power rail of the power supply
         component.";

      list rail {
        config false;
        key "name";
        description
          "Contains operational state of each power rail of a power supply
           component.";

        leaf name {
          type leafref {
            path "../state/name";
          }
          description
            "The name of the power rail.";
        }

        container state {
          description
            "Contains operational state of a rail of a power supply
            component.";
          uses google-pins-power-supply-rails-state;
        }
      }
    }
  }

  grouping google-pins-power-supply-state {
    description
      "Google specific state for power supply component.";

    leaf type {
      type identityref {
        base POWER_SUPPLY_TYPE;
      }
      description
        "Type of power supply component.";
    }

    leaf frequency {
      type oc-types:ieeefloat32;
      units hertz;
      description
        "Maps to READ_FREQUENCY in PMBUS standard.";
    }

    leaf commanded-frequency {
      type oc-types:ieeefloat32;
      units hertz;
      description
        "Maps to FREQUENCY_SWITCH in PMBUS standard.";
    }

    leaf manufacturer-status {
      type binary;
      description
        "Maps to STATUS_MFR_SPECIFIC in PMBUS standard.";
    }

    leaf status-gpio {
      type binary;
      description
        "Maps to STATUS_GPIO in PMBUS standard.";
    }

  }

  grouping google-pins-storage-state {
    description
      "Google specific state for storage component.";

    leaf io-errors {
      type oc-yang:counter64;
      description
        "Count of input/output errors.";
    }

    leaf write-amplification-factor {
      type decimal64 {
        fraction-digits 2;
      }
      description
        "Numerical value to measure write-amplification.";
    }

    leaf raw-read-error-rate {
      type decimal64 {
        fraction-digits 1;
      }
      description
        "Stores data related to the rate of hardware read errors that
        occurred when reading data from a disk surface";
    }

    leaf throughput-performance {
      type decimal64 {
        fraction-digits 1;
      }
      units Mbps;
      description
        "Overall (general) throughput performance of a hard disk drive.
        Throughput is data transfer rate of a drive, which can be measured by
        writing a large file to disk using special file generator tools, then
        reading back the file";
    }

    leaf reallocated-sector-count {
      type uint64;
      description
        "Count of reallocated sectors";
    }

    leaf power-on-seconds {
      type uint64;
      units seconds;
      description
        "Number present the count of time in power-on state.";
    }

    leaf ssd-life-left {
      type uint64;
      description
        "Indicates the approximate SSD life left, in terms of program/erase
        cycles or available reserved blocks";
    }

    leaf avg-erase-count {
      type uint32;
      description
        "This attribute is used to collect the average number of user area
        block erasures.";
    }

    leaf max-erase-count {
      type uint32;
      description
        "This attribute is used to collect the maximum number of user area
        block erasures.";
    }

    leaf power-cycle-count {
      type uint32;
      description
        "Total number of power cycles that the device has experienced over
        its lifetime. A cycle is defined as the device transitioning from the
        OFF state to the ON state.";
    }

    leaf uncorrectable-sector-count-on-line {
      type uint32;
      description
        "Total number of uncorrectable ECC errors including errors occurring
        while reading non-user data that were reported back to the host.";
    }

    leaf num-pure-spare {
      type uint32;
      description
        "Total number of remaining spare blocks expressed as a function of
        maximum reserved blocks provisioned in the drive.";
    }

    leaf num-initial-invalid-block {
      type uint32;
      description
        "Total number of factory bad blocks. Factory bad blocks are bad blocks
        found during initial card.";
    }

    leaf slc-total-erase-count {
      type uint32;
      description
        "Total number of SLC block erase count in SLC area that the device has
        experienced over its lifetime.";
    }

    leaf slc-max-erase-count {
      type uint32;
      description
        "Maximum number of SLC block erase count in SLC area that the device has
        experienced over its lifetime.";
    }

    leaf slc-min-erase-count {
      type uint32;
      description
        "Minimum number of SLC block erase count in SLC area that the device has
        experienced over its lifetime.";
    }

    leaf slc-avg-erase-count {
      type uint32;
      description
        "Average number of SLC block erase count in SLC area that the device has
        experienced over its lifetime.";
    }

    leaf tlc-total-erase-count {
      type uint32;
      description
        "Total number of TLC block erase count in TLC area that the device has
        experienced over its lifetime.";
    }

    leaf tlc-max-erase-count {
      type uint32;
      description
        "Maximum number of TLC block erase count in TLC area that the device has
        experienced over its lifetime.";
    }

    leaf tlc-min-erase-count {
      type uint32;
      description
        "Minimum number of TLC block erase count in TLC area that the device has
        experienced over its lifetime.";
    }

    leaf tlc-avg-erase-count {
      type uint32;
      description
        "Average number of TLC block erase count in TLC area that the device has
        experienced over its lifetime.";
    }

    leaf wear-leveling-count {
      type uint32;
      description
        "Total number of wear leveling events over the life of the drive.";
    }

    leaf program-fail-count {
      type uint32;
      description
        "Total number of flash program failure events over the life of the
        drive.";
    }

    leaf erase-fail-count {
      type uint32;
      description
        "Total number of flash erase failure events over the life of the
        drive.";
    }

    leaf power-off-retract-count {
      type uint32;
      description
        "Total number of unexpected or sudden power loss events. A sudden or
        unexpected power loss event is defined as power being removed from the
        device without it having acknowledged the successful completion of a
        STANDBY IMMEDIATE command.";
    }

    leaf hardware-ecc-recovered {
      type uint32;
      description
        "Total number of correctable ECC errors, including errors occurring
        while reading non-user data, expressed as a function of total data read
        over the interface.";
    }

    leaf reallocation-event-count {
      type uint32;
      description
        "Total number of uncorrectable ECC errors, including errors occurring
        while reading non-user data, expressed as a function of total data read
        over the interface.";
    }

    leaf udma-crc-errors-count {
      type uint32;
      description
        "Total number of SATA FIS interface CRC errors encountered over the life
        of the drive, including reads and writes.";
    }

    leaf available-reserved-space {
      type uint32;
      description
        "The number represents a ratio of the reserved block count.";
    }

    leaf write-sector-count {
      type uint32;
      description
        "Total number of user data LBAs written by the drive over its
        lifetime.";
    }

    leaf read-sector-count {
      type uint32;
      description
        "Total number of user data LBAs read by the drive over its lifetime.";
    }

    leaf flash-write-count {
      type uint32;
      description
        "Total number of user data committed to the drive’s media over its
        lifetime.";
    }
  }

  grouping google-pins-sensor {
    description
      "Top level grouping for the augments for the sensor component.";

    container sensor {
      description
        "Google specific augments for the sensor component.";

      container config {
        description
          "Configuration data for the sensor component.";
      }

      container state {
        config false;
        description
          "Operational state data for the sensor component.";

        uses google-pins-sensor-state;
      }
    }
  }

  grouping google-pins-sensor-state {
    description
      "Google specific state of the sensor component.";

    leaf sensor-type {
      type identityref {
        base SENSOR_TYPE;
      }
      description
        "Type of sensor component.";
    }
  }

  grouping google-pins-fpga-reset-causes {
    description
      "Top level grouping for fpga reset causes.";

    container reset-causes {
      description
        "Top level container for fpga reset causes.";

      list reset-cause {
        config false;
        key "index";
        description
          "List of reset-causes contains the last few reset causes.";

        leaf index {
          type leafref {
            path "../state/index";
          }
          description
            "References the reset cause index, index 0 is the most recent
            reset cause index, index 1 is the reset cause before that and
            so on.";
        }

        container state {
          description
            "Operational state data for fpga reset cause.";
          leaf index {
            type uint8;
            description
              "fpga reset cause index.";
          }
          leaf cause {
            type enumeration {
              enum UNKNOWN {
                description
                  "fpga reset cause is unknown.";
              }
              enum POWER {
                description
                  "fpga was just powered up.";
              }
              enum SWITCH {
                description
                  "fpga was reset from front panel switch.";
              }
              enum WATCHDOG {
                description
                  "fpga was reset as watchdog timer expired.";
              }
              enum SOFTWARE {
                description
                  "fpga was reset by software request.";
              }
              enum EMULATOR {
                description
                  "fpga was reset by emulator (COP header) request.";
              }
              enum CPU {
                description
                  "fpga was reset by a request to reset CPU.";
              }
            }
            description
              "fpga reset causes in GPINS.";
          }
        }
      }
    }
  }

  augment "/oc-platform:components/oc-platform:component/oc-platform:state" {
    description
      "Adds Google specific state for components in the platform module.";

    uses google-pins-platform-state;
  }

  grouping google-pins-hardware-security-module {
    description
      "Top level grouping for the augments for hardware security module.";

    container hardware-security-module {
      description
        "Google specific augments for hardware security module.";

      container config {
        description
          "Configuration data for the hardware security module.";
      }

      container state {
        config false;
        description
          "Operational state data for the hardware security module.";

        uses google-pins-hardware-security-module-state;
      }
    }
  }

  grouping google-pins-hardware-security-module-state {
    description
      "Google specific state of the hardware security module.";

    leaf secure-payload-enforced {
      type boolean;
      description
        "Set to true if secure boot is enabled.";
    }

    leaf payload-version {
      type string;
      description
        "Payload version as seen by the hardware security module.";
    }

    leaf payload-signature-type {
      type enumeration {
        enum INVALID {
          description
            "Payload signature type is invalid.";
        }
        enum UNSIGNED {
          description
            "Payload signature type is unsigned.";
        }
        enum DEV {
          description
            "Payload signature type is development.";
        }
        enum PROD {
          description
            "Payload signature type is production.";
        }
      }
      description
        "Signature type of payload.";
    }

    leaf authorization-record-present {
      type boolean;
      description
        "Set to true if authorization record is present.";
    }

    leaf authorized-capabilities-register {
      type uint32;
      description
        "Bitmap of authorized capabilities in each record.";
    }
  }

  grouping google-pins-boot-loader {
    description
      "Top level grouping for the augments for the boot-loader component.";

    container boot-loader {
      description
        "Google specific augments for the boot-loader component.";

      container config {
        description
          "Configuration data for the boot-loader component.";
      }

      container state {
        config false;
        description
          "Operational state data for the boot-loader component.";

        uses google-pins-boot-loader-state;
      }
    }
  }

  grouping google-pins-boot-loader-state {
    description
      "Google specific state of the boot-loader component.";

    leaf boot-loader-type {
      type identityref {
        base BOOT_LOADER_TYPE;
      }
      description
        "Type of boot-loader component.";
    }
  }

  grouping google-pins-temperature-state {
    description
      "Google specific temperature state for platform component.";

    leaf low-warn-threshold {
      type decimal64 {
        fraction-digits 1;
      }
      units celcius;
      description
        "The threshold for temperature below which an alarm with severity
        warning may be raised.";
    }

    leaf low-critical-threshold {
      type decimal64 {
        fraction-digits 1;
      }
      units celcius;
      description
        "The threshold for temperature below which an alarm with severity
        critical may be raised.";
    }

    leaf high-warn-threshold {
      type decimal64 {
        fraction-digits 1;
      }
      units celcius;
      description
        "The threshold for temperature above which an alarm with severity
        warning may be raised.";
    }

    leaf high-critical-threshold {
      type decimal64 {
        fraction-digits 1;
      }
      units celcius;
      description
        "The threshold for temperature above which an alarm with severity
        critical may be raised.";
    }
  }

  grouping google-pins-diag-top {
    description
      "grouping for blackhole and congestion events";

    container blackhole {
      description
      "grouping for blackhole and congestion events";

      leaf in-discard-events{
        description
          "The number of in-discard-events found by the diag blackhole
          feature";
        type oc-yang:counter64;
      }

      leaf out-discard-events{
        description
          "The number of out-discard-events found by the diag blackhole
          feature";
        type oc-yang:counter64;
      }

      leaf in-error-events{
        description
          "The number of in-error-events found by the diag blackhole feature";
        type oc-yang:counter64;
      }

      leaf lpm-miss-events{
        description
          "The number of lpm-miss-events found by the diag blackhole
          feature";
        type oc-yang:counter64;
      }

      leaf fec-not-correctable-events{
        description
          "The number of fec-not-correctable-events found by the diag blackhole
          feature";
        type oc-yang:counter64;
      }

      leaf memory-error-events{
        description
          "The number of memory-error-events found by the diag blackhole
          feature";
        type oc-yang:counter64;
      }

      leaf blackhole-events{
        description
          "The number of blackhole-events found by the diag blackhole
          feature";
        type oc-yang:counter64;
      }
    }

    container congestion {
      description
        "container for congestion events";

      leaf congestion-events{
        description
          "The number of congestion-events found by the diag congestion
          feature";
        type oc-yang:counter64;
      }
    }
  }

  augment "/oc-platform:components/oc-platform:component/oc-platform:state/oc-platform:temperature" {
    description
      "Adds Google specific temperature state for platform components.";

    uses google-pins-temperature-state;
  }

  augment "/oc-platform:components/oc-platform:component/oc-platform:fan/oc-platform:state" {
    description
      "Adds Google specific state for fan component.";

    uses google-pins-fan-state;
  }

  augment "/oc-platform:components/oc-platform:component/oc-platform:power-supply" {
    description
      "Adds Google specific state for power-supply component.";

    uses google-pins-power-supply-rails-top;
  }

  augment "/oc-platform:components/oc-platform:component/oc-platform:power-supply/oc-platform:state" {
    description
      "Adds Google specific state for power-supply component.";

    uses google-pins-power-supply-state;
  }

  augment "/oc-platform:components/oc-platform:component/oc-platform:storage/oc-platform:state" {
    description
      "Adds Google specific state for storage component.";

    uses google-pins-storage-state;
  }

  augment "/oc-platform:components/oc-platform:component/oc-transceiver:transceiver/oc-transceiver:state" {
    description
      "Adds Google specific state for transceiver component.";

    uses google-pins-transceiver-state;
  }

  augment "/oc-platform:components/oc-platform:component/oc-transceiver:transceiver/oc-transceiver:state/oc-transceiver:input-power" {
    description
      "Adds Google specific input power state for transceiver component.";

    uses google-pins-transceiver-power-state;
  }

  augment "/oc-platform:components/oc-platform:component/oc-transceiver:transceiver/oc-transceiver:state/oc-transceiver:output-power" {
    description
      "Adds Google specific output power state for transceiver component.";

    uses google-pins-transceiver-power-state;
  }

  augment "/oc-platform:components/oc-platform:component/oc-platform:integrated-circuit/oc-platform:state" {
    description
      "Adds Google specific state for integrated-circuit component.";

    uses google-pins-diag-top;
  }

  augment "/oc-platform:components/oc-platform:component" {
    description
      "Adds Google specific state for platform component.";

    uses google-pins-fpga;
    uses google-pins-sensor;
    uses google-pins-boot-loader;
    uses google-pins-hardware-security-module;
  }

  // rpc statements
  // notification statements
}
